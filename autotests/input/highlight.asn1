-- comment with FIXME alerts
-- example code taken from https://en.wikipedia.org/wiki/ASN.1

FooProtocol DEFINITIONS ::= BEGIN
    /** Multiline comment
     *  with ### alerts
     */
    FooQuestion ::= SEQUENCE {
        trackingNumber INTEGER(0..199),
        question       IA5String
    }

    FooAnswer ::= SEQUENCE {
        questionNumber INTEGER(10..20),
        answer         BOOLEAN
    }

    FooHistory ::= SEQUENCE {
        questions SEQUENCE(SIZE(0..10)) OF FooQuestion,
        answers   SEQUENCE(SIZE(1..10)) OF FooAnswer,
        anArray   SEQUENCE(SIZE(100))  OF INTEGER(0..1000)
    }

END

-- exmaples from ERA FCB barcode.asn
ASN-Module DEFINITIONS AUTOMATIC TAGS ::= BEGIN
    IssuingData  	::=  SEQUENCE	{
        -- [...]
        -- currency of the price: ISO4217 currency codes
        currency			IA5String (SIZE(3)) 		DEFAULT "EUR"
        -- [...]
	}

END
